module msncc-provider-impl {
    yang-version 1;
    namespace "urn:opendaylight:params:xml:ns:yang:lispflowmapping:netconf:impl";
    prefix "lfm-nc-impl";

    import config { prefix config; revision-date 2013-04-05; }
    import opendaylight-md-sal-binding { prefix mdsal; revision-date 2013-10-28; }

    description
        "This module contains the base YANG definitions for lispflowmapping-netconf-connector implementation.";

    revision "2014-07-06" {
        description
            "Initial revision.";
    }

    identity msncc-provider-impl {
            base config:module-type;
            config:java-name-prefix MsNCCProvider;
    }

    augment "/config:modules/config:module/config:configuration" {
        case msncc-provider-impl {
            when "/config:modules/config:module/config:type = 'msncc-provider-impl'";
            
            container rpc-registry {
            	uses config:service-ref {
            		refine type {
            			mandatory true;
            			config:required-identity mdsal:binding-rpc-registry;
            		}
            	}
            }        
        }
    }
}
